package RWXAcqTags {
	//  This package was auto-generated from the RockWorx acquisition ontology

	//  https://w3id.org/rockworx/acq#AcquisitionGate
	metadata def AcquisitionGate;

	//  https://w3id.org/rockworx/acq#AuthorityReference
	metadata def AuthorityReference;

	//  https://w3id.org/rockworx/acq#KeyPerformanceParameter
	metadata def KeyPerformanceParameter;

	//  https://w3id.org/rockworx/acq#ProgramRisk
	metadata def ProgramRisk;

	//  https://w3id.org/rockworx/acq#TechnicalReview
	metadata def TechnicalReview;

	//  https://w3id.org/rockworx/acq/sysml#assessedAt
	connection def assessedAt {
		end sub;
		end obj;
	}

	//  https://w3id.org/rockworx/acq/sysml#indicatesRisk
	connection def indicatesRisk {
		end sub;
		end obj;
	}

	//  https://w3id.org/rockworx/acq#informs
	connection def informs {
		end sub;
		end obj;
	}

	//  https://w3id.org/rockworx/acq/sysml#satisfies
	connection def satisfies {
		end sub;
		end obj;
	}

	//  https://w3id.org/rockworx/acq/sysml#verifies
	connection def verifies {
		end sub;
		end obj;
	}

	//  http://www.w3.org/ns/prov#wasDerivedFrom
	connection def wasDerivedFrom {
		end sub;
		end obj;
	}

}
